FME workspace YR forecasts.fmw

Bookmark: datetime: request dt in utc
Creator_2
    GEOMTYPE = Geometry Object
    NUM = 3
    CREATED -> DateTimeStamper
DateTimeStamper
    DATETIME_ATTR = origin_utc
    INCLUDE_FRAC_SECONDS = NO
    INCLUDE_OFFSET = NO
    STAMP_TYPE = datetime
    TIMEZONE = utc
    -> AttributeCreator_2
AttributeCreator_2
    ATTR_TABLE:
      SET_TO stream = FME_CONDITIONAL:DEFAULT_VALUE'_FME_NO_OP_'BOOL_OP;OR;COMPOSITE_TEST;1;TEST @Value(_creation_instance) = 0'Queenstown'BOOL_OP;OR;COMPOSITE_TEST;1;TEST @Value(_creation_instance) = 1'Wanaka'BOOL_OP;OR;COMPOSITE_TEST;1;TEST @Value(_creation_instance) = 2'Cromwell'FME_NUM_CONDITIONS4___
      SET_TO interval = 1h
      SET_TO lat = FME_CONDITIONAL:DEFAULT_VALUE'_FME_NO_OP_'BOOL_OP;OR;COMPOSITE_TEST;1;TEST @Value(_creation_instance) = 0'-45.0302'BOOL_OP;OR;COMPOSITE_TEST;1;TEST @Value(_creation_instance) = 1'-44.6957'BOOL_OP;OR;COMPOSITE_TEST;1;TEST @Value(_creation_instance) = 2'-45.0406'FME_NUM_CONDITIONS4___
      SET_TO long = FME_CONDITIONAL:DEFAULT_VALUE'_FME_NO_OP_'BOOL_OP;OR;COMPOSITE_TEST;1;TEST @Value(_creation_instance) = 0'168.6615'BOOL_OP;OR;COMPOSITE_TEST;1;TEST @Value(_creation_instance) = 1'169.1357'BOOL_OP;OR;COMPOSITE_TEST;1;TEST @Value(_creation_instance) = 2'169.2119'FME_NUM_CONDITIONS4___
      SET_TO altitude = FME_CONDITIONAL:DEFAULT_VALUE'_FME_NO_OP_'BOOL_OP;OR;COMPOSITE_TEST;1;TEST @Value(_creation_instance) = 0'300'BOOL_OP;OR;COMPOSITE_TEST;1;TEST @Value(_creation_instance) = 1'300'BOOL_OP;OR;COMPOSITE_TEST;1;TEST @Value(_creation_instance) = 2'300'FME_NUM_CONDITIONS4___
    -> DateTimeConverter
DateTimeConverter
    DATETIME_ATTR = origin_utc
    OUT_FORMAT = %Y-%m-%dT%H:%M:%SZ
    PASSTHROUGH = NO
    REPAIR_INPUT = YES
    -> Junction
    -> Junction_3
Junction_3
    -> Junction_4
Junction
    -> Junction_2

Bookmark: load: 2snowflake or agol every 10min past the hour
Junction_4
    -> DateTimeConverter_Output
Note: Snowwflake can automate python .. .easier over time / other process: / 1. remove data older than 3 months / 2. workbench / script will work calculate rolling ARIs
DateTimeConverter_Output: Inspector
Junction_10
    -> DateTimeConverter_2_Output
DateTimeConverter_2_Output: Logger
    LOG_FEATURE = LOG_ONLY
    MAXCOORDS = 20
    MAXFEATS = 20
    MESSAGE = Feature is:
    SEVERITY = INFO

Bookmark: sites: set up three sites to collect weather forecast data
Junction_2
    -> _yr
Note: _yr [HTTPCaller] / Request: / Request URL: https://api.met.no/weatherapi/locationforecast/2.0/complete? / HTTP Method: GET / Query String Parameters: / Name / Value / lat / @Value(lat) / lon / @Value(long) / altitude / @Value(altitude) / Headers: / Name / Value / Accept / application/xml / User-Agent / Queenstown Lakes District Council
_yr: HTTPCaller
    ADDITIONAL_URL_PARAMETERS = lat;@Value(lat) lon;@Value(long) altitude;@Value(altitude)
    CONNECTION_TIMEOUT_LENGTH = 60
    CUSTOM_HEADERS = Accept;application/xml User-Agent;Queenstown Lakes District Council
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _yr
    TARGET_ATTR_ENCODING = auto-detect
    TARGET_URL = https://api.met.no/weatherapi/locationforecast/2.0/complete?
    TRANSFER_TIMEOUT_LENGTH = 90
    USE_COOKIES = No
    VERIFY_SSL_CERTIFICATES = Yes
    -> JSONFragmenter_3
    <REJECTED> -> _yr__Rejected_
_yr__Rejected_: Logger
    LOG_FEATURE = LOG_ONLY
    MAXCOORDS = 20
    MAXFEATS = 20
    MESSAGE = Feature is:
    SEVERITY = INFO
JSONFragmenter_3
    EXPLODE_FORMAT = JSON
    EXTRACT_ATTR = No
    JSON_ATTR = _yr
    JSON_QUERY = json["properties"]["timeseries"][*]
    READ_FROM_FILE = NO
    REJECT_EMPTY_LISTS = YES
    FRAGMENTS -> JSONExtractor_3
JSONExtractor_3
    EXTRACT_QUERY_TABLE = DateTime json["time"] Value json["data"]["next_1_hours"]["details"]["precipitation_amount"]
    JSON_DOCUMENT = @Value(_yr)
    READ_FROM_FILE = NO
    EVALUATED -> Junction_7
Junction_7
    -> Junction_8

Bookmark: transform: format table
Junction_8
    -> Tester
Tester
    BOOL_OP = OR
    TEST_CLAUSE = TEST @Value(json_index) < 63
    TEST_MODE = TEST
    PASSED -> AttributeCreator
Note: AttributeCreator [AttributeCreator] / New Attributes: Output AttributeValueTypeqc_flagFME_CONDITIONAL:DEFAULT_VALUE'400'BOOL_OP;OR;COMPOSITE_TEST;1;TEST <at>Value<openparen>json_index<closeparen> < 2'600'BOOL_OP;OR;COMPOSITE_TEST;1;TEST <at>Value<openparen ... varchar(200)unitsmm/hrbufferinvalidFALSEbufferDateTime@DateTimeFormat(@Value(DateTime),%Y%m%d%H%M%S)varchar(200)Value@round(@Value(Value),3)varchar(200)
AttributeCreator
    ATTR_TABLE:
      SET_TO qc_flag (varchar(200)) = FME_CONDITIONAL:DEFAULT_VALUE'400'BOOL_OP;OR;COMPOSITE_TEST;1;TEST @Value(json_index) < 2'600'BOOL_OP;OR;COMPOSITE_TEST;1;TEST @Value(json_index) < 4'500'FME_NUM_CONDITIONS3___
      SET_TO units (buffer) = mm/hr
      SET_TO invalid (buffer) = FALSE
      SET_TO DateTime (varchar(200)) = @DateTimeFormat(@Value(DateTime),%Y%m%d%H%M%S)
      SET_TO Value (varchar(200)) = @round(@Value(Value),3)
    -> NullAttributeMapper
NullAttributeMapper
    ATTRCHOICE = Selected Attributes
    ATTRLIST = Value
    NEW_VALUE = 0
    NULL_TREATMENT = New Value
    OTHER_VALUE = null
    SOURCE_ATTR_VAL = Null Empty "Missing (Selected Attributes Only)"
    -> AttributeManager
AttributeManager
    ATTR_TABLE:
      RENAME_SET_VALUE DateTime > datetime (varchar(200))
      RENAME_SET_VALUE Value > value (varchar(200))
      REMOVE interval (varchar(200))
      REMOVE lat (varchar(200))
      REMOVE long (varchar(200))
      REMOVE altitude (varchar(200))
      REMOVE _creation_instance (uint64)
      REMOVE origin_utc (buffer)
      REMOVE _yr (buffer)
      REMOVE _http_status_code (buffer)
      REMOVE json_type (buffer)
      REMOVE json_index (uint32)
    -> Junction_5
Junction_5
    -> Junction_6

Bookmark: transform: statistics
Junction_6
    -> StatisticsCalculator_2
StatisticsCalculator_2
    CALCULATION_MODE = NUMERIC
    FEAT_STATS = datetime,NUMERIC_MODE,MIN,,,,,,,,,,,,
    GROUP_BY = stream
    COMPLETE -> AttributeRenamer
AttributeRenamer
    ATTR_TABLE = RENAME_SET_DEFAULT datetime.min > origin
    MISSING_INPUT_ATTRS = REMOVE
    -> DateTimeConverter_2
DateTimeConverter_2
    DATETIME_ATTR = datetime origin
    OUT_FORMAT = %Y-%m-%dT%H:%M:%S
    PASSTHROUGH = NO
    REPAIR_INPUT = YES
    -> Junction_9
Junction_9
    -> Junction_10
